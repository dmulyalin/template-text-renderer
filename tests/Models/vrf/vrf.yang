module vrf {
    yang-version "1.1";

    namespace "http://ttr/test-2";
    
    prefix "ttr-vrf";
  
    leaf interface {
        type string;
    }
    leaf template {
        mandatory true;
        type string;
    }
    leaf device {
        mandatory true;
        type string;
    }
    leaf description{
        type string;
    }
    leaf vrf_name {
        mandatory true;
        type string;
    }
    leaf vrf_rd {
        mandatory true;
        type string;
    }
    leaf vrf_rt {
        type string;
    }
}
